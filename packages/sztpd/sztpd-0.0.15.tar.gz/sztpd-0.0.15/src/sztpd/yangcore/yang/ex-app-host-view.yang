module ex-app-host-view {
  yang-version 1.1;
  namespace "https://watsen.net/host-view";
  prefix host;

  import wn-app {
    prefix wnapp;
  }

  organization
    "Watsen Networks (https://watsen.net)";

  description
    "INTERNAL USE ONLY, NOT SHARED

     This module defines a data model for a multi-tenant application.
     Copyright (c) 2021 Watsen Networks.  All rights reserved.

     INTERNAL USE ONLY, NOT SHARED";

  revision YYYY-MM-DD {
    description
      "Initial version";
  }

  /**********************************************************/
  /* Protocol-Accessible Nodes (only if module implemented) */
  /**********************************************************/

  uses wnapp:yangcore-host-view-grouping {
    augment "tenants/tenant" {
      leaf TENANT-ONLY-LEAF {
        type string;
      }
    }
  }
  leaf HOST-ONLY-LEAF {
    type string;
  }

}
