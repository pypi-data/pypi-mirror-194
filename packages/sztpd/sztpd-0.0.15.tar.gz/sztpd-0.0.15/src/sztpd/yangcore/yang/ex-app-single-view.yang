module ex-app-single-view {
  yang-version 1.1;
  namespace "https://watsen.net/single-view";
  prefix single-view;

  import wn-app {
    prefix wnapp;
  }

  organization
    "Watsen Networks (https://watsen.net)";

  description
    "INTERNAL USE ONLY, NOT SHARED

     This module defines a data model for a single-view application.
     Copyright (c) 2021 Watsen Networks.  All rights reserved.

     INTERNAL USE ONLY, NOT SHARED";

  revision YYYY-MM-DD {
    description
      "Initial version";
  }


  /**********************************************************/
  /* Protocol-Accessible Nodes (only if module implemented) */
  /**********************************************************/

  uses wnapp:yangcore-single-view-grouping;
  leaf SINGLE-ONLY-LEAF {
    type string;
  }

}
